-- prim.asn1: leaf types, exercised without composition.
--
-- REAL is present so that asn1c emits REAL.c and the negative test can prove
-- an unsupported type fails loudly rather than emitting anything.
Prim DEFINITIONS AUTOMATIC TAGS ::= BEGIN

Colour ::= ENUMERATED { red(0), green(1), blue(2) }

-- Identifiers asn1c keeps only in the generated headers, never in the runtime
-- descriptors: Level gets "0 /* No specifics */" and Flags points at the
-- generic asn_SPC_BIT_STRING_specs. The annotation sidecar recovers them.
Level ::= INTEGER { low(0), medium(5), high(10) }
Flags ::= BIT STRING { keyCert(0), crlSign(1), dataEncipher(3) }

Holder ::= SEQUENCE {
    flag  BOOLEAN,
    void  NULL,
    small INTEGER,
    col   Colour,
    data  OCTET STRING,
    bits  BIT STRING,
    oid   OBJECT IDENTIFIER,
    roid  RELATIVE-OID,
    real  REAL OPTIONAL
}

END
