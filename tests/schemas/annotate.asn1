-- annotate.asn1: input for vn-annotate, the annotation table generator.
--
-- Every identifier here carries a hyphen on purpose: asn1c rewrites hyphens to
-- underscores when it forms C enum names (asn1c_misc.c, asn1c_make_identifier),
-- and X.680 12.3 admits letters, digits and hyphens only, so a table that
-- copies the C spelling emits invalid value notation. `auto` probes what asn1c
-- does to an identifier that collides with a C keyword.
Annotate DEFINITIONS AUTOMATIC TAGS ::= BEGIN

Threshold ::= INTEGER { light-red(1), dark-blue(2), auto(3) }

Caps ::= BIT STRING { key-cert(0), crl-sign(1), data-encipher(3) }

-- Two INTEGER representations other than the plain `long` that Threshold gets,
-- both of which asn1c reaches for on its own and neither of which used to be
-- offered the annotation table.
--
-- (0..MAX) makes the field `unsigned long` and sets field_unsigned; a range
-- wider than asn1c is willing to hold natively makes it a buffer-backed
-- INTEGER_t instead.
Count ::= INTEGER { none(0), all(255) } (0..MAX)
Wide  ::= INTEGER { brim(4294967295) } (0..4294967295)

-- An inline BIT STRING member. asn1c writes the enum but no
-- `typedef BIT_STRING_t Slot__marks_t;`, because the member is declared inside
-- struct Slot, so the generator has to take the representation from there.
Slot ::= SEQUENCE {
    marks BIT STRING { first-mark(0), third-mark(2) },
    tail  OCTET STRING
}

-- 11.8 says a name is the same whether its hyphen is a HYPHEN-MINUS or a
-- NON-BREAKING HYPHEN, so every kind of identifier the reader matches needs a
-- hyphen in it: a member name, a named number, a named bit and an enumerator.
Hyphen-Probe ::= SEQUENCE {
    first-field  INTEGER { one-value(1) },
    second-field ENUMERATED { plain-red(0), plain-blue(1) },
    third-field  BIT STRING { low-bit(0), high-bit(1) }
}

-- A hyphen in the *type* name: the runtime descriptor says "Pe-Level" while
-- the generated header says Pe_Level, so the table key needs the same mapping
-- as the value names.
Pe-Level ::= INTEGER { rock-bottom(0), deep-black(9) }

-- ENUMERATED identifiers are retained at runtime and the encoder never
-- consults the table for them, but the generator still scans the enum, so its
-- names must be mapped like every other.
Mood ::= ENUMERATED { very-happy(0), so-so(1) }

-- An inline INTEGER member. asn1c scopes its enum as Box__mode with a double
-- underscore, which is a C name boundary rather than a former hyphen and must
-- survive the mapping untouched.
Box ::= SEQUENCE {
    mode INTEGER { slow-start(0), fast(1) },
    pad  OCTET STRING
}

-- The same inline definition inside a CHOICE. asn1c scopes it as Pick__speed
-- exactly as for a SEQUENCE member, so the alternative has to establish the
-- scope on the way down or the entry is unreachable.
Pick ::= CHOICE {
    speed INTEGER { crawl(0), sprint(1) },
    label VisibleString
}

-- One level deeper. asn1c names these by the whole path that reaches them
-- (Outer__inner__x, Outer__ring__Member__y), while the anonymous inline
-- SEQUENCE is called just "SEQUENCE" at runtime, so the scope has to
-- accumulate on the way down rather than be rebuilt from the nearest parent.
Outer ::= SEQUENCE {
    inner SEQUENCE { x INTEGER { alpha(1) } },
    ring  SEQUENCE OF SEQUENCE { y INTEGER { beta(2) } }
}

END
